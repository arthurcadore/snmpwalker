IPSEC-IKEACTION-MIB DEFINITIONS ::= BEGIN


IMPORTS
    MODULE-IDENTITY, OBJECT-TYPE, Integer32, Unsigned32
                                        FROM SNMPv2-SMI
                                             -- [rfc2578]

    TEXTUAL-CONVENTION, RowStatus, TruthValue,
    TimeStamp, StorageType, VariablePointer
                                        FROM SNMPv2-TC
                                             -- [rfc2579]

    MODULE-COMPLIANCE, OBJECT-GROUP
                                        FROM SNMPv2-CONF
                                             -- [rfc2580]

    SnmpAdminString
                                        FROM SNMP-FRAMEWORK-MIB
                                             -- [rfc3411]

    InetAddressType, InetAddress, InetPortNumber
                                        FROM INET-ADDRESS-MIB
                                             -- [rfc4001]

    spdActions, SpdIPPacketLogging, spdEndGroupInterface
                                        FROM IPSEC-SPD-MIB
                                             -- [rfcZZZZ]
    ;

--
-- module identity
--

ipiaMIB MODULE-IDENTITY
    LAST-UPDATED "200404211200Z"    -- 05 September 2006
    ORGANIZATION "IETF IP Security Policy Working Group"
    CONTACT-INFO "Michael Baer
                  P.O. Box 72682
                  Davis, CA 95617
                  Phone: +1 530 902 3131
                  Email: baerm@tislabs.com

                  Ricky Charlet
                  Email: rcharlet@alumni.calpoly.edu

                  Wes Hardaker
                  Sparta, Inc.
                  P.O. Box 382
                  Davis, CA  95617
                  Phone: +1 530 792 1913
                  Email: hardaker@tislabs.com

                  Robert Story
                  Revelstone Software
                  PO Box 1812
                  Tucker, GA 30085
                  Phone: +1 770 617 3722
                  Email: rstory@sparta.com

                  Cliff Wang
                  ARO/North Carolina State University
                  4300 S. Miami Blvd.
                  RTP, NC 27709
                  E-Mail: cliffwangmail@yahoo.com"

    DESCRIPTION
     "The MIB module for defining IKE actions for managing IPsec
      Security Policy.
      Copyright (C) The Internet Society (2006). This version of
      this MIB module is part of RFC YYYY, see the RFC itself for
      full legal notices."

-- Revision History

    REVISION     "200404211200Z"    -- 05 September 2006
    DESCRIPTION  "Initial version, published as RFC YYYY."
    -- RFC-editor assigns YYYY

    ::= { spdActions 2 }


IpsaCredentialType ::= TEXTUAL-CONVENTION
    STATUS   current
    DESCRIPTION
        "."
    SYNTAX      INTEGER { reserved(0),
                          unknown(1),
                          sharedSecret(2),
                          x509(3),
                          kerberos(4) }

IpsecDoiIdentType ::= TEXTUAL-CONVENTION
    DISPLAY-HINT "d"
    STATUS      current
    DESCRIPTION "."
    REFERENCE   "RFC 2407 sections 4.4.5, 4.6.2.1, and 6.9"
    SYNTAX      Unsigned32 (0..255)

IpsaIdentityFilter ::=  TEXTUAL-CONVENTION
    STATUS   current
    DESCRIPTION
        "."
    SYNTAX      OCTET STRING (SIZE(1..256))


--
-- groups of related objects
--

ipiaConfigObjects         OBJECT IDENTIFIER
     ::= { ipiaMIB 1 }
ipiaNotificationObjects   OBJECT IDENTIFIER
     ::= { ipiaMIB 2 }
-- ipiaConformanceObjects    OBJECT IDENTIFIER
--     ::= { ipiaMIB 3 }

--
-- Textual Conventions
--

IkeEncryptionAlgorithm ::= TEXTUAL-CONVENTION
    DISPLAY-HINT "d"
    STATUS      current
    DESCRIPTION "Values for encryption algorithms negotiated
                for the ISAKMP SA by IKE in Phase I.  These are
                values for SA Attrbute type Encryption
                Algorithm (1).

                Unused values <= 65000 are reserved to IANA.
                Currently assigned values at the time of this
                writing:

                    reserved(0),        -- reserved in IKE
                    desCbc(1),          -- RFC 2405
                    ideaCbc(2),
                    blowfishCbc(3),
                    rc5R16B64Cbc(4),    -- RC5 R16 B64 CBC
                    tripleDesCbc(5),    -- 3DES CBC
                    castCbc(6),
                    aesCbc(7)
                Values 65001-65535 are for private use among
                mutually consenting parties."
    REFERENCE   "RFC 2409 appendix A,
                IANA"
    SYNTAX      Unsigned32 (0..65535)

IkeAuthMethod ::= TEXTUAL-CONVENTION
    DISPLAY-HINT "d"
    STATUS      current
    DESCRIPTION "Values for authentication methods negotiated
                for the ISAKMP SA by IKE in Phase I.  These are
                values for SA Attrbute type Authentication
                Method (3).

                Unused values <= 65000 are reserved to IANA.

                    reserved(0),        -- reserved in IKE
                    preSharedKey(1),
                    dssSignatures(2),
                    rsaSignatures(3),
                    encryptionWithRsa(4),
                    revisedEncryptionWithRsa(5),
                    reservedDontUse6(6), -- not to be used
                    reservedDontUse7(7), -- not to be used
                    ecdsaSignatures(8)

                Values 65001-65535 are for private use among
                mutually consenting parties."
    REFERENCE   "RFC 2409 appendix A,
                IANA"
    SYNTAX      Unsigned32 (0..65535)

IkeHashAlgorithm ::= TEXTUAL-CONVENTION
    DISPLAY-HINT "d"
    STATUS      current
    DESCRIPTION "Values for hash algorithms negotiated
                for the ISAKMP SA by IKE in Phase I.  These are
                values for SA Attrbute type Hash Algorithm (2).

                Unused values <= 65000 are reserved to IANA.
                Currently assigned values at the time of this
                writing:

                    reserved(0),        -- reserved in IKE
                    md5(1),             -- RFC 1321
                    sha(2),             -- FIPS 180-1
                    tiger(3),
                    sha256(4),
                    sha384(5),
                    sha512(6)

                Values 65001-65535 are for private use among
                mutually consenting parties."
    REFERENCE   "RFC 2409 appendix A,
                IANA"
    SYNTAX      Unsigned32 (0..65535)

IkeGroupDescription ::= TEXTUAL-CONVENTION
    DISPLAY-HINT "d"
    STATUS      current
    DESCRIPTION "Values for Oakley key computation groups for
                Diffie-Hellman exchange negotiated for the ISAKMP
                SA by IKE in Phase I.  They are also used in Phase II
                when perfect forward secrecy is in use.  These are
                values for SA Attrbute type Group Description (4).

                Unused values <= 32767 are reserved to IANA.
                Currently assigned values at the time of this
                writing:

                    none(0),            -- reserved in IKE, used
                                        -- in MIBs to reflect that
                                        -- none of the predefined
                                        -- groups are used
                    modp768(1),         -- default 768-bit MODP group
                    modp1024(2),        -- alternate 1024-bit MODP
                                        -- group
                    ec2nGF155(3),       -- EC2N group on Galois
                                        -- Field GF[2^155]
                    ec2nGF185(4),       -- EC2N group on Galois
                                        -- Field GF[2^185]
                    ec2nGF163Random(6), -- EC2N group on Galois
                                        -- Field GF[2^163],
                                        -- random seed
                    ec2nGF163Koblitz(7),
                                        -- EC2N group on Galois
                                        -- Field GF[2^163],
                                        -- Koblitz curve
                    ec2nGF283Random(8), -- EC2N group on Galois
                                        -- Field GF[2^283],
                                        -- random seed
                    ec2nGF283Koblitz(9),
                                        -- EC2N group on Galois
                                        -- Field GF[2^283],
                                        -- Koblitz curve
                    ec2nGF409Random(10),
                                        -- EC2N group on Galois
                                        -- Field GF[2^409],
                                        -- random seed
                    ec2nGF409Koblitz(11),
                                        -- EC2N group on Galois
                                        -- Field GF[2^409],
                                        -- Koblitz curve
                    ec2nGF571Random(12),
                                        -- EC2N group on Galois
                                        -- Field GF[2^571],
                                        -- random seed
                    ec2nGF571Koblitz(13)
                                        -- EC2N group on Galois
                                        -- Field GF[2^571],
                                        -- Koblitz curve

                Values 32768-65535 are for private use among
                mutually consenting parties."
    REFERENCE   "RFC 2409 appendix A,
                IANA"
    SYNTAX      Unsigned32 (0..65535)

IpsecDoiSecProtocolId ::= TEXTUAL-CONVENTION
    DISPLAY-HINT "d"
    STATUS      current
    DESCRIPTION "These are the IPsec DOI values for the Protocol-Id
                field in an ISAKMP Proposal Payload, and in all
                Notification Payloads.

                They are also used as the Protocol-ID In the
                Notification Payload and the Delete Payload.

                Currently assigned values at the time of this
                writing:

                    reserved(0),        -- reserved in DOI
                    protoIsakmp(1),     -- message protection
                                        -- required during Phase I
                                        -- of the IKE protocol
                    protoIpsecAh(2),    -- IP packet authentication
                                        -- via Authentication Header
                    protoIpsecEsp(3),   -- IP packet confidentiality
                                        -- via Encapsulating
                                        -- Security Payload
                    protoIpcomp(4)      -- IP payload compression

                The values 249-255 are reserved for private use
                amongst cooperating systems."
    REFERENCE   "RFC 2407 section 4.4.1"
    SYNTAX      Unsigned32 (0..255)

--
-- credential filter table
--

ipiaCredentialFilterTable OBJECT-TYPE
    SYNTAX      SEQUENCE OF IpiaCredentialFilterEntry
    MAX-ACCESS  not-accessible
    STATUS      current
    DESCRIPTION
        "This table is used to provide credentials for IKE
         identities.
         It can be used to for filters which are matched to
         credentials of IKE peers, where the credentials in question
         have been obtained from an IKE phase 1 exchange.  They MAY
         be X.509 certificates, Kerberos tickets, etc...

         It can also be used to provide credentials for local IKE
         identities."
    ::= { ipiaConfigObjects 3 }

ipiaCredentialFilterEntry OBJECT-TYPE
    SYNTAX      IpiaCredentialFilterEntry
    MAX-ACCESS  not-accessible
    STATUS      current
    DESCRIPTION
        "A row defining a particular credential filter"
    INDEX   { ipiaCredFiltName }
    ::= { ipiaCredentialFilterTable 1 }

IpiaCredentialFilterEntry ::= SEQUENCE {
    ipiaCredFiltName                      SnmpAdminString,
    ipiaCredFiltCredentialType            IpsaCredentialType,
    ipiaCredFiltMatchFieldName            OCTET STRING,
    ipiaCredFiltMatchFieldValue           OCTET STRING,
    ipiaCredFiltAcceptCredFrom            OCTET STRING,
    ipiaCredFiltLastChanged               TimeStamp,
    ipiaCredFiltStorageType               StorageType,
    ipiaCredFiltRowStatus                 RowStatus
}

ipiaCredFiltName OBJECT-TYPE
    SYNTAX      SnmpAdminString (SIZE(1..32))
    MAX-ACCESS  not-accessible
    STATUS      current
    DESCRIPTION
        "The administrative name of this filter."
    ::= { ipiaCredentialFilterEntry 1 }

ipiaCredFiltCredentialType OBJECT-TYPE
    SYNTAX      IpsaCredentialType
    MAX-ACCESS  read-create
    STATUS      current
    DESCRIPTION
        "The credential type that is expected for this filter to
         succeed."
    DEFVAL { x509 }
    ::= { ipiaCredentialFilterEntry 2 }

ipiaCredFiltMatchFieldName OBJECT-TYPE
    SYNTAX      OCTET STRING (SIZE(0..256))
    MAX-ACCESS  read-create
    STATUS      current
    DESCRIPTION
        "The piece of the credential to match against.  Examples:
         serialNumber, signatureAlgorithm, issuerName or
         subjectName.

         For credential types without fields (e.g. shared secret),
         this field SHOULD be left empty, and the entire credential
         will be matched against the ipiaCredFiltMatchFieldValue."
    ::= { ipiaCredentialFilterEntry 3 }

ipiaCredFiltMatchFieldValue OBJECT-TYPE
    SYNTAX      OCTET STRING (SIZE(1..4096))
    MAX-ACCESS  read-create
    STATUS      current
    DESCRIPTION
        "The value that the field indicated by the
         ipiaCredFiltMatchFieldName MUST match against for the
         filter to be considered TRUE."
    ::= { ipiaCredentialFilterEntry 4 }

ipiaCredFiltAcceptCredFrom OBJECT-TYPE
    SYNTAX      OCTET STRING(SIZE(1..117))
    MAX-ACCESS  read-create
    STATUS      current
    DESCRIPTION
        "This value is used to look up a row in the
         ipiaIpsecCredMngServiceTable for the Certificate Authority
         (CA) Information.  This value is empty if there is no CA
         used for this filter."
    ::= { ipiaCredentialFilterEntry 5 }

ipiaCredFiltLastChanged OBJECT-TYPE
    SYNTAX      TimeStamp
    MAX-ACCESS  read-only
    STATUS      current
    DESCRIPTION
        "The value of sysUpTime when this row was last modified or
         created either through SNMP SETs or by some other external
         means."
    ::= { ipiaCredentialFilterEntry 6 }

ipiaCredFiltStorageType OBJECT-TYPE
    SYNTAX      StorageType
    MAX-ACCESS  read-create
    STATUS      current
    DESCRIPTION
        "The storage type for this row.  Rows in this table which
         were created through an external process MAY have a storage
         type of readOnly or permanent.

         For a storage type of permanent, none of the columns have
         to be writable."
    DEFVAL { nonVolatile }
    ::= { ipiaCredentialFilterEntry 7 }

ipiaCredFiltRowStatus OBJECT-TYPE
    SYNTAX      RowStatus
    MAX-ACCESS  read-create
    STATUS      current
    DESCRIPTION
        "This object indicates the conceptual status of this row.

         The value of this object has no effect on whether other
         objects in this conceptual row can be modified.

         If active, this object MUST remain active if it is
         referenced by an active row in another table.  An attempt
         to set it to anything other than active while it is
         referenced by an active row in another table MUST result in
         an inconsistentValue error."
    ::= { ipiaCredentialFilterEntry 8 }

--
-- ipiaIkeActionTable
--

ipiaIkeActionTable OBJECT-TYPE
    SYNTAX          SEQUENCE OF IpiaIkeActionEntry
    MAX-ACCESS  not-accessible
    STATUS          current
    DESCRIPTION
        "The ipiaIkeActionTable contains a list of the parameters
         used for an IKE phase 1 SA DOI negotiation.  See the
         corresponding table ipiaIkeActionProposalsTable for a list
         of proposals contained within a given IKE Action."
    ::= { ipiaConfigObjects 6 }

ipiaIkeActionEntry OBJECT-TYPE
    SYNTAX          IpiaIkeActionEntry
    MAX-ACCESS  not-accessible
    STATUS          current
    DESCRIPTION
        "The ipiaIkeActionEntry lists the IKE negotiation
         attributes."
    INDEX       { ipiaIkeActName }
    ::= { ipiaIkeActionTable 1 }

IpiaIkeActionEntry ::= SEQUENCE {
    ipiaIkeActName                              SnmpAdminString,
    ipiaIkeActParametersName                    SnmpAdminString,
    ipiaIkeActThresholdDerivedKeys              Integer32,
    ipiaIkeActExchangeMode                      INTEGER,
    ipiaIkeActAgressiveModeGroupId              IkeGroupDescription,
    ipiaIkeActIdentityType                      IpsecDoiIdentType,
    ipiaIkeActIdentityContext                   SnmpAdminString,
    ipiaIkeActPeerName                          SnmpAdminString,
    ipiaIkeActDoActionLogging                   TruthValue,
    ipiaIkeActDoPacketLogging                   SpdIPPacketLogging,
    ipiaIkeActVendorId                          OCTET STRING,
    ipiaIkeActLastChanged                       TimeStamp,
    ipiaIkeActStorageType                       StorageType,
    ipiaIkeActRowStatus                         RowStatus
}

ipiaIkeActName OBJECT-TYPE
    SYNTAX           SnmpAdminString (SIZE(1..32))
    MAX-ACCESS       not-accessible
    STATUS           current
    DESCRIPTION
        "This object contains the name of this ikeAction entry."
    ::= { ipiaIkeActionEntry 1 }

ipiaIkeActParametersName OBJECT-TYPE
    SYNTAX           SnmpAdminString (SIZE(1..32))
    MAX-ACCESS       read-create
    STATUS           current
    DESCRIPTION
        "This object is administratively assigned to reference a row
         in the ipiaSaNegotiationParametersTable where additional
         parameters affecting this action can be found.

         An attempt to set this object to a value that does not
         exist in the ipiaSaNegotiationParametersTable MUST result
         in an inconsistentValue error."
    ::= { ipiaIkeActionEntry 2 }

ipiaIkeActThresholdDerivedKeys OBJECT-TYPE
    SYNTAX           Integer32 (0..100)
    MAX-ACCESS       read-create
    STATUS           current
    DESCRIPTION
        "ipiaIkeActThresholdDerivedKeys specifies what percentage
         of the derived key limit (see the LifetimeDerivedKeys
         property of IKEProposal) can expire before IKE SHOULD
         attempt to renegotiate the IKE phase 1 security
         association."
    DEFVAL           { 100 }
    ::= { ipiaIkeActionEntry 3 }

ipiaIkeActExchangeMode OBJECT-TYPE
    SYNTAX           INTEGER { main(1), agressive(2) }
    MAX-ACCESS       read-create
    STATUS           current
    DESCRIPTION
        "ipiaIkeActExchangeMode specifies the IKE Phase 1
         negotiation mode."
    DEFVAL { main }
    ::= { ipiaIkeActionEntry 4 }

ipiaIkeActAgressiveModeGroupId OBJECT-TYPE
    SYNTAX           IkeGroupDescription
    MAX-ACCESS       read-create
    STATUS           current
    DESCRIPTION
        "The values to be used for Diffie-Hellman exchange."
    ::= { ipiaIkeActionEntry 5 }

ipiaIkeActIdentityType OBJECT-TYPE
    SYNTAX      IpsecDoiIdentType
    MAX-ACCESS  read-create
    STATUS      current
    DESCRIPTION
        "This column along with ipiaIkeActIdentityContext and
         endpoint information is used to refer an
         ipiaIkeIdentityEntry in the ipiaIkeIdentityTable."
    ::= { ipiaIkeActionEntry 6 }

ipiaIkeActIdentityContext   OBJECT-TYPE
    SYNTAX           SnmpAdminString (SIZE(1..32))
    MAX-ACCESS       read-create
    STATUS           current
    DESCRIPTION
        "This column, along with ipiaIkeActIdentityType and endpoint
         information, is used to refer to an ipiaIkeIdentityEntry in
         the ipiaIkeIdentityTable."
    ::= { ipiaIkeActionEntry 7 }

ipiaIkeActPeerName OBJECT-TYPE
    SYNTAX      SnmpAdminString(SIZE(0..32))
    MAX-ACCESS  read-create
    STATUS      current
    DESCRIPTION
        "This object indicates the peer id name of the IKE peer.
         This object can be used to look up the peer id value,
         address, credentials and other values in the
         ipiaPeerIdentityTable."
    ::= { ipiaIkeActionEntry 8 }

ipiaIkeActDoActionLogging OBJECT-TYPE
    SYNTAX      TruthValue
    MAX-ACCESS  read-create
    STATUS      current
    DESCRIPTION
        "ikeDoActionLogging specifies whether or not an audit
         message SHOULD be logged when this ike SA is created."
     DEFVAL { false }
    ::= { ipiaIkeActionEntry 9 }

ipiaIkeActDoPacketLogging OBJECT-TYPE
    SYNTAX      SpdIPPacketLogging
    MAX-ACCESS  read-create
    STATUS      current
    DESCRIPTION
        "ikeDoPacketLogging specifies whether or not an audit
         message SHOULD be logged and if there is logging, how many
         bytes of the packet to place in the notification."
     DEFVAL { -1 }
    ::= { ipiaIkeActionEntry 10 }

ipiaIkeActVendorId    OBJECT-TYPE
    SYNTAX           OCTET STRING (SIZE(0..65535))
    MAX-ACCESS       read-create
    STATUS           current
    DESCRIPTION
        "Vendor ID Payload.  A value of NULL means that Vendor ID
         payload will be neither generated nor accepted.  A non-NULL
         value means that a Vendor ID payload will be generated
         (when acting as an initiator) or is expected (when acting
         as a responder)."
    DEFVAL { "" }
    ::= { ipiaIkeActionEntry 11 }

ipiaIkeActLastChanged OBJECT-TYPE
    SYNTAX           TimeStamp
    MAX-ACCESS       read-only
    STATUS           current
    DESCRIPTION
        "The value of sysUpTime when this row was last modified or
         created either through SNMP SETs or by some other external
         means."
    ::= { ipiaIkeActionEntry 12 }

ipiaIkeActStorageType OBJECT-TYPE
    SYNTAX           StorageType
    MAX-ACCESS       read-create
    STATUS           current
    DESCRIPTION
        "The storage type for this row.  Rows in this table which
         were created through an external process MAY have a storage
         type of readOnly or permanent.

         For a storage type of permanent, none of the columns have
         to be writable."
    DEFVAL { nonVolatile }
    ::= { ipiaIkeActionEntry 13 }

ipiaIkeActRowStatus OBJECT-TYPE
    SYNTAX           RowStatus
    MAX-ACCESS       read-create
    STATUS           current
    DESCRIPTION
        "This object indicates the conceptual status of this row.

         The value of this object has no effect on whether other
         objects in this conceptual row can be modified.

         This object MUST NOT be set to destroy if referred to by
         other rows in other action tables.  An attempt to set it to
         anything other than active while it is referenced by an
         active row in another table MUST result in an
         inconsistentValue error."
    ::= { ipiaIkeActionEntry 14 }


--
-- IPsec action definition table
--


ipiaIpsecActionTable OBJECT-TYPE
    SYNTAX      SEQUENCE OF IpiaIpsecActionEntry
    MAX-ACCESS  not-accessible
    STATUS      current
    DESCRIPTION
        "The ipiaIpsecActionTable contains a list of the parameters
         used for an IKE phase 2 IPsec DOI negotiation."
    ::= { ipiaConfigObjects 7 }

ipiaIpsecActionEntry OBJECT-TYPE
    SYNTAX      IpiaIpsecActionEntry
    MAX-ACCESS  not-accessible
    STATUS      current
    DESCRIPTION
        "The ipiaIpsecActionEntry lists the IPsec negotiation
         attributes."
    INDEX       { ipiaIpsecActName }
    ::= { ipiaIpsecActionTable 1 }

IpiaIpsecActionEntry ::= SEQUENCE {
    ipiaIpsecActName                          SnmpAdminString,
    ipiaIpsecActParametersName                SnmpAdminString,
    ipiaIpsecActProposalsName                 SnmpAdminString,
    ipiaIpsecActUsePfs                        TruthValue,
    ipiaIpsecActVendorId                      OCTET STRING,
    ipiaIpsecActGroupId                       IkeGroupDescription,
    ipiaIpsecActPeerGatewayIdName             OCTET STRING,
    ipiaIpsecActUseIkeGroup                   TruthValue,
    ipiaIpsecActGranularity                   INTEGER,
    ipiaIpsecActMode                          INTEGER,
    ipiaIpsecActDFHandling                    INTEGER,
    ipiaIpsecActDoActionLogging               TruthValue,
    ipiaIpsecActDoPacketLogging               SpdIPPacketLogging,
    ipiaIpsecActLastChanged                   TimeStamp,
    ipiaIpsecActStorageType                   StorageType,
    ipiaIpsecActRowStatus                     RowStatus
}

ipiaIpsecActName OBJECT-TYPE
    SYNTAX      SnmpAdminString (SIZE(1..32))
    MAX-ACCESS  not-accessible
    STATUS      current
    DESCRIPTION
         "ipiaIpsecActName is the name of the ipsecAction entry."
    ::= { ipiaIpsecActionEntry 1 }


ipiaIpsecActParametersName OBJECT-TYPE
    SYNTAX           SnmpAdminString (SIZE(1..32))
    MAX-ACCESS       read-create
    STATUS           current
    DESCRIPTION
        "This object is used to reference a row in the
         ipiaSaNegotiationParametersTable where additional
         parameters affecting this action can be found.

         An attempt to set this column to a value that does not
         exist in the ipiaSaNegotiationParametersTable MUST result
         in an inconsistentValue error."
    ::= { ipiaIpsecActionEntry 2 }

ipiaIpsecActProposalsName OBJECT-TYPE
    SYNTAX           SnmpAdminString (SIZE(1..32))
    MAX-ACCESS       read-create
    STATUS           current
    DESCRIPTION
        "This object is used to reference one or more rows in the
         ipiaIpsecProposalsTable where an ordered list of proposals
         affecting this action can be found.

         An attempt to set this column to a value that does not
         exist in the ipiaIpsecProposalsTable MUST result in an
         inconsistentValue error."
    ::= { ipiaIpsecActionEntry 3 }

ipiaIpsecActUsePfs OBJECT-TYPE
    SYNTAX      TruthValue
    MAX-ACCESS  read-create
    STATUS      current
    DESCRIPTION
        "This MIB object specifies whether or not perfect forward
         secrecy is used when refreshing keys.  A value of true
         indicates that PFS SHOULD be used."
    ::= { ipiaIpsecActionEntry 4 }

ipiaIpsecActVendorId OBJECT-TYPE
    SYNTAX      OCTET STRING (SIZE(0..255))
    MAX-ACCESS  read-create
    STATUS      current
    DESCRIPTION
        "The VendorID property is used to identify vendor-defined
         key exchange GroupIDs."
    ::= { ipiaIpsecActionEntry 5 }

ipiaIpsecActGroupId OBJECT-TYPE
    SYNTAX      IkeGroupDescription
    MAX-ACCESS  read-create
    STATUS      current
    DESCRIPTION
        "This object specifies the Diffie-Hellman group to use for
         phase 2 when the object ipiaIpsecActUsePfs is true and the
         object ipiaIpsecActUseIkeGroup is false.  If the GroupID
         number is from the vendor-specific range (32768-65535), the
         VendorID qualifies the group number."
    ::= { ipiaIpsecActionEntry 6 }

ipiaIpsecActPeerGatewayIdName OBJECT-TYPE
    SYNTAX      OCTET STRING (SIZE(0..116))
    MAX-ACCESS  read-create
    STATUS      current
    DESCRIPTION
        "This object indicates the peer id name of the peer
         gateway.  This object can be used to look up the peer id
         value, address and other values in the
         ipiaPeerIdentityTable.  This object is used when initiating
         a tunnel SA.  This object is not used for transport SAs.
         If no value is set and ipiaIpsecActMode is tunnel, the peer
         gateway is determined from the source or destination
         address of the packet."
    ::= { ipiaIpsecActionEntry 7 }

ipiaIpsecActUseIkeGroup OBJECT-TYPE
    SYNTAX      TruthValue
    MAX-ACCESS  read-create
    STATUS      current
    DESCRIPTION
        "This object specifies whether or not to use the same
         GroupId for phase 2 as was used in phase 1.  If UsePFS is
         false, this entry SHOULD be ignored."
    ::= { ipiaIpsecActionEntry 8 }

ipiaIpsecActGranularity OBJECT-TYPE
    SYNTAX      INTEGER { subnet(1), address(2), protocol(3),
                          port(4) }
    MAX-ACCESS  read-create
    STATUS      current
    DESCRIPTION
        "This object specifies how the proposed selector for the
         security association will be created.  The selector is
         created by using the FilterList information.  The selector
         can be subnet, address, porotocol, or port."
    ::= { ipiaIpsecActionEntry 9 }

ipiaIpsecActMode OBJECT-TYPE
    SYNTAX      INTEGER { tunnel(1), transport(2) }
    MAX-ACCESS  read-create
    STATUS      current
    DESCRIPTION
        "This object specifies the encapsulation of the IPsec SA
         to be negotiated."
    DEFVAL { tunnel }
    ::= { ipiaIpsecActionEntry 10 }

ipiaIpsecActDFHandling OBJECT-TYPE
    SYNTAX      INTEGER { copy(1), set(2), clear(3) }
    MAX-ACCESS  read-create
    STATUS      current
    DESCRIPTION
        "This object specifies the processing of DF bit by the
         negotiated IPsec tunnel.
         1 - DF bit is copied.
         2 - DF bit is set.
         3 - DF bit is cleared."
    DEFVAL { copy }
    ::= { ipiaIpsecActionEntry 11 }

ipiaIpsecActDoActionLogging OBJECT-TYPE
    SYNTAX      TruthValue
    MAX-ACCESS  read-create
    STATUS      current
    DESCRIPTION
        "ipiaIpsecActDoActionLogging specifies whether or not an
         audit message SHOULD be logged when this ipsec SA is
         created."
     DEFVAL { false }
    ::= { ipiaIpsecActionEntry 12 }

ipiaIpsecActDoPacketLogging OBJECT-TYPE
    SYNTAX      SpdIPPacketLogging
    MAX-ACCESS  read-create
    STATUS      current
    DESCRIPTION
        "ipiaIpsecActDoPacketLogging specifies whether or not an
         audit message SHOULD be logged and if there is logging, how
         many bytes of the packet to place in the notification."
     DEFVAL { -1 }
    ::= { ipiaIpsecActionEntry 13 }

ipiaIpsecActLastChanged OBJECT-TYPE
    SYNTAX      TimeStamp
    MAX-ACCESS  read-only
    STATUS      current
    DESCRIPTION
        "The value of sysUpTime when this row was last modified or
         created either through SNMP SETs or by some other external
         means."
    ::= { ipiaIpsecActionEntry 14 }

ipiaIpsecActStorageType OBJECT-TYPE
    SYNTAX      StorageType
    MAX-ACCESS  read-create
    STATUS      current
    DESCRIPTION
        "The storage type for this row.  Rows in this table which
         were created through an external process MAY have a storage
         type of readOnly or permanent.

         For a storage type of permanent, none of the columns have
         to be writable."
    DEFVAL { nonVolatile }
    ::= { ipiaIpsecActionEntry 15 }

ipiaIpsecActRowStatus OBJECT-TYPE
    SYNTAX      RowStatus
    MAX-ACCESS  read-create
    STATUS      current
    DESCRIPTION
        "This object indicates the conceptual status of this row.

         The value of this object has no effect on whether other
         objects in this conceptual row can be modified.

         If active, this object MUST remain active if it is
         referenced by an active row in another table.  An attempt
         to set it to anything other than active while it is
         referenced by an active row in another table MUST result in
         an inconsistentValue error."
    ::= { ipiaIpsecActionEntry 16 }
--
-- ipiaIkeActionProposalsTable proposals contained within a ikeAction
--

ipiaIkeActionProposalsTable OBJECT-TYPE
    SYNTAX      SEQUENCE OF IpiaIkeActionProposalsEntry
    MAX-ACCESS   not-accessible
    STATUS      current
    DESCRIPTION
        "This table contains a list of all ike proposal names found
         within a given IKE Action."
    ::= { ipiaConfigObjects 9 }

ipiaIkeActionProposalsEntry OBJECT-TYPE
    SYNTAX      IpiaIkeActionProposalsEntry
    MAX-ACCESS  not-accessible
    STATUS      current
    DESCRIPTION
        "a row containing one ike proposal reference"
    INDEX   { ipiaIkeActName, ipiaIkeActPropPriority }
    ::= { ipiaIkeActionProposalsTable 1 }

IpiaIkeActionProposalsEntry ::= SEQUENCE {
    ipiaIkeActPropPriority                   Integer32,
    ipiaIkeActPropName                       SnmpAdminString,
    ipiaIkeActPropLastChanged                TimeStamp,
    ipiaIkeActPropStorageType                StorageType,
    ipiaIkeActPropRowStatus                  RowStatus
}

ipiaIkeActPropPriority OBJECT-TYPE
    SYNTAX      Integer32 (0..65535)
    MAX-ACCESS  not-accessible
    STATUS      current
    DESCRIPTION
        "The numeric priority of a given contained proposal inside
         an ike Action.  This index SHOULD be used to order the
         proposals in an IKE Phase I negotiation, lowest value first
         (i.e. 0 first, then 1,2,etc...)."
    ::= { ipiaIkeActionProposalsEntry 1 }

ipiaIkeActPropName OBJECT-TYPE
    SYNTAX      SnmpAdminString (SIZE(1..32))
    MAX-ACCESS  read-create
    STATUS      current
    DESCRIPTION
        "The administratively assigned name that can be used to
         reference a set of values contained within the
         ipiaIkeProposalTable.

         An attempt to set this object to a value that doesn't exist
         in the ipiaIkeProposalTable MUST result in an
         inconsistentValue error."
    ::= { ipiaIkeActionProposalsEntry 2 }

ipiaIkeActPropLastChanged OBJECT-TYPE
    SYNTAX           TimeStamp
    MAX-ACCESS       read-only
    STATUS           current
    DESCRIPTION
        "The value of sysUpTime when this row was last modified or
         created either through SNMP SETs or by some other external
         means."
    ::= { ipiaIkeActionProposalsEntry 3 }

ipiaIkeActPropStorageType OBJECT-TYPE
    SYNTAX           StorageType
    MAX-ACCESS       read-create
    STATUS           current
    DESCRIPTION
        "The storage type for this row.  Rows in this table which
         were created through an external process MAY have a storage
         type of readOnly or permanent.

         For a storage type of permanent, none of the columns have
         to be writable."
    DEFVAL { nonVolatile }
    ::= { ipiaIkeActionProposalsEntry 4 }

ipiaIkeActPropRowStatus OBJECT-TYPE
    SYNTAX           RowStatus
    MAX-ACCESS       read-create
    STATUS           current
    DESCRIPTION
        "This object indicates the conceptual status of this row.

         The value of this object has no effect on whether other
         objects in this conceptual row can be modified.

         If active, this object MUST remain active unless one of the
         following two conditions are met.  An attempt to set it to
         anything other than active while the following conditions
         are not met MUST result in an inconsistentValue error.  The
         two conditions are:

         I.  No active row in the ipiaIkeActionTable exists
             which has a matching ipiaIkeActName.

         II. Or at least one other active row in this table has a
             matching ipiaIkeActName."
    ::= { ipiaIkeActionProposalsEntry 5 }


--
-- IKE proposal definition table
--

ipiaIkeProposalTable OBJECT-TYPE
    SYNTAX      SEQUENCE OF IpiaIkeProposalEntry
    MAX-ACCESS  not-accessible
    STATUS      current
    DESCRIPTION
        "This table contains a list of IKE proposals which are used
         in an IKE negotiation."
    ::= { ipiaConfigObjects 10 }

ipiaIkeProposalEntry OBJECT-TYPE
    SYNTAX      IpiaIkeProposalEntry
    MAX-ACCESS  not-accessible
    STATUS      current
    DESCRIPTION
        "One IKE proposal entry."
    INDEX       { ipiaIkeActPropName }
    ::= { ipiaIkeProposalTable 1 }

IpiaIkeProposalEntry ::= SEQUENCE {
    ipiaIkePropLifetimeDerivedKeys     Unsigned32,
    ipiaIkePropCipherAlgorithm         IkeEncryptionAlgorithm,
    ipiaIkePropCipherKeyLength         Unsigned32,
    ipiaIkePropCipherKeyRounds         Unsigned32,
    ipiaIkePropHashAlgorithm           IkeHashAlgorithm,
    ipiaIkePropPrfAlgorithm            INTEGER,
    ipiaIkePropVendorId                OCTET STRING,
    ipiaIkePropDhGroup                 IkeGroupDescription,
    ipiaIkePropAuthenticationMethod    IkeAuthMethod,
    ipiaIkePropMaxLifetimeSecs         Unsigned32,
    ipiaIkePropMaxLifetimeKB           Unsigned32,
    ipiaIkePropLastChanged             TimeStamp,
    ipiaIkePropStorageType             StorageType,
    ipiaIkePropRowStatus               RowStatus
}

ipiaIkePropLifetimeDerivedKeys OBJECT-TYPE
    SYNTAX      Unsigned32
    MAX-ACCESS  read-create
    STATUS      current
    DESCRIPTION
        "ipiaIkePropLifetimeDerivedKeys specifies the number of
         times that a phase 1 key will be used to derive a phase 2
         key before the phase 1 security association needs
         renegotiated."
    ::= { ipiaIkeProposalEntry 1 }

ipiaIkePropCipherAlgorithm OBJECT-TYPE
    SYNTAX      IkeEncryptionAlgorithm
    MAX-ACCESS  read-create
    STATUS      current
    DESCRIPTION
        "ipiaIkePropCipherAlgorithm specifies the proposed phase 1
         security association encryption algorithm."
    ::= { ipiaIkeProposalEntry 2 }

ipiaIkePropCipherKeyLength OBJECT-TYPE
    SYNTAX      Unsigned32
    MAX-ACCESS  read-create
    STATUS      current
    DESCRIPTION
        "This object specifies, in bits, the key length for
         the cipher algorithm used in IKE Phase 1 negotiation."
    ::= { ipiaIkeProposalEntry 3 }

ipiaIkePropCipherKeyRounds OBJECT-TYPE
    SYNTAX      Unsigned32
    MAX-ACCESS  read-create
    STATUS      current
    DESCRIPTION
        "This object specifies the number of key rounds for
         the cipher algorithm used in IKE Phase 1 negotiation."
    ::= { ipiaIkeProposalEntry 4 }

ipiaIkePropHashAlgorithm OBJECT-TYPE
    SYNTAX      IkeHashAlgorithm
    MAX-ACCESS  read-create
    STATUS      current
    DESCRIPTION
        "ipiaIkePropHashAlgorithm specifies the proposed phase 1
         security assocation hash algorithm."
    ::= { ipiaIkeProposalEntry 5 }

ipiaIkePropPrfAlgorithm OBJECT-TYPE
    SYNTAX      INTEGER { reserved(0) }
    MAX-ACCESS  read-create
    STATUS      current
    DESCRIPTION
        "ipPRFAlgorithm specifies the proposed phase 1 security
         association psuedo-random function.

         Note: currently no prf algorithms are defined."
    ::= { ipiaIkeProposalEntry 6 }

ipiaIkePropVendorId OBJECT-TYPE
    SYNTAX      OCTET STRING (SIZE(0..255))
    MAX-ACCESS  read-create
    STATUS      current
    DESCRIPTION
        "The VendorID property is used to identify vendor-defined
         key exchange GroupIDs."
    ::= { ipiaIkeProposalEntry 7 }

ipiaIkePropDhGroup OBJECT-TYPE
    SYNTAX      IkeGroupDescription
    MAX-ACCESS  read-create
    STATUS      current
    DESCRIPTION
        "This object specifies the proposed phase 1 security
         association Diffie-Hellman group"
    ::= { ipiaIkeProposalEntry 8 }

ipiaIkePropAuthenticationMethod OBJECT-TYPE
    SYNTAX      IkeAuthMethod
    MAX-ACCESS  read-create
    STATUS      current
    DESCRIPTION
        "This object specifies the proposed authentication
         method for the phase 1 security association."
    ::= { ipiaIkeProposalEntry 9 }

ipiaIkePropMaxLifetimeSecs OBJECT-TYPE
    SYNTAX      Unsigned32
    MAX-ACCESS  read-create
    STATUS      current
    DESCRIPTION
        "ipiaIkePropMaxLifetimeSecs specifies the maximum amount of
         time to propose a security association remain valid.

         A value of 0 indicates that the default lifetime of
         8 hours SHOULD be used."
    ::= { ipiaIkeProposalEntry 10 }

ipiaIkePropMaxLifetimeKB OBJECT-TYPE
    SYNTAX      Unsigned32
    MAX-ACCESS  read-create
    STATUS      current
    DESCRIPTION
        "ipiaIkePropMaxLifetimeKB specifies the maximum kilobyte
         lifetime to propose a security association remain valid."
    ::= { ipiaIkeProposalEntry 11 }

ipiaIkePropLastChanged OBJECT-TYPE
    SYNTAX      TimeStamp
    MAX-ACCESS  read-only
    STATUS      current
    DESCRIPTION
        "The value of sysUpTime when this row was last modified or
         created either through SNMP SETs or by some other external
         means."
    ::= { ipiaIkeProposalEntry 12 }

ipiaIkePropStorageType OBJECT-TYPE
    SYNTAX      StorageType
    MAX-ACCESS  read-create
    STATUS      current
    DESCRIPTION
        "The storage type for this row.  Rows in this table which
         were created through an external process MAY have a storage
         type of readOnly or permanent.

         For a storage type of permanent, none of the columns have
         to be writable."
    DEFVAL { nonVolatile }
    ::= { ipiaIkeProposalEntry 13 }

ipiaIkePropRowStatus OBJECT-TYPE
    SYNTAX      RowStatus
    MAX-ACCESS  read-create
    STATUS      current
    DESCRIPTION
        "This object indicates the conceptual status of this row.

         The value of this object has no effect on whether other
         objects in this conceptual row can be modified.

         If active, this object MUST remain active if it is
         referenced by an active row in another table.  An attempt
         to set it to anything other than active while it is
         referenced by an active row in another table MUST result in
         an inconsistentValue error."
    ::= { ipiaIkeProposalEntry 14 }


--
-- ipiaIpsecProposalsTable
--


ipiaIpsecProposalsTable OBJECT-TYPE
    SYNTAX      SEQUENCE OF IpiaIpsecProposalsEntry
    MAX-ACCESS  not-accessible
    STATUS      current
    DESCRIPTION
        "This table lists one or more IPsec proposals for
         IPsec actions."
    ::= { ipiaConfigObjects 11 }

ipiaIpsecProposalsEntry OBJECT-TYPE
    SYNTAX      IpiaIpsecProposalsEntry
    MAX-ACCESS  not-accessible
    STATUS      current
    DESCRIPTION
        "An entry containing (possibly a portion of) a proposal."
    INDEX       { ipiaIpsecPropName, ipiaIpsecPropPriority,
                  ipiaIpsecPropProtocolId }
    ::= { ipiaIpsecProposalsTable 1 }

IpiaIpsecProposalsEntry ::= SEQUENCE {
    ipiaIpsecPropName                   SnmpAdminString,
    ipiaIpsecPropPriority               Integer32,
    ipiaIpsecPropProtocolId             IpsecDoiSecProtocolId,
    ipiaIpsecPropTransformsName         SnmpAdminString,
    ipiaIpsecPropLastChanged            TimeStamp,
    ipiaIpsecPropStorageType            StorageType,
    ipiaIpsecPropRowStatus              RowStatus
}

ipiaIpsecPropName OBJECT-TYPE
    SYNTAX      SnmpAdminString (SIZE(1..32))
    MAX-ACCESS  not-accessible
    STATUS      current
    DESCRIPTION
        "The name of this proposal."
    ::= { ipiaIpsecProposalsEntry 1 }

ipiaIpsecPropPriority OBJECT-TYPE
    SYNTAX      Integer32 (0..65535)
    MAX-ACCESS  not-accessible
    STATUS      current
    DESCRIPTION
        "The priority level (AKA sequence level) of this proposal.
         A lower number indicates a higher precedence (0 before 1,
         etc..)."
    ::= { ipiaIpsecProposalsEntry 2 }

ipiaIpsecPropProtocolId OBJECT-TYPE
    SYNTAX      IpsecDoiSecProtocolId
    MAX-ACCESS  not-accessible
    STATUS      current
    DESCRIPTION
        "The protocol Id for the transforms for this proposal.  The
         protoIsakmp(1) value is not valid for this object.  This
         object, along with the ipiaIpsecPropTransformsName, is the
         index into the ipiaIpsecTransformsTable."
    ::= { ipiaIpsecProposalsEntry 3 }

ipiaIpsecPropTransformsName OBJECT-TYPE
    SYNTAX      SnmpAdminString (SIZE(1..32))
    MAX-ACCESS  read-create
    STATUS      current
    DESCRIPTION
        "The name of the transform or group of transforms for this
         protocol.  This object, along with the
         ipiaIpsecPropProtocolId, is the index into the
         ipiaIpsecTransformsTable.

         An attempt to set this object to a value that does not
         exist in the ipiaIpsecTransformTable MUST result in an
         inconsistentValue error."
    ::= { ipiaIpsecProposalsEntry 4 }

ipiaIpsecPropLastChanged OBJECT-TYPE
    SYNTAX      TimeStamp
    MAX-ACCESS  read-only
    STATUS      current
    DESCRIPTION
        "The value of sysUpTime when this row was last modified or
         created either through SNMP SETs or by some other external
         means."
    ::= { ipiaIpsecProposalsEntry 5 }

ipiaIpsecPropStorageType OBJECT-TYPE
    SYNTAX      StorageType
    MAX-ACCESS  read-create
    STATUS      current
    DESCRIPTION
        "The storage type for this row.  Rows in this table which
         were created through an external process MAY have a storage
         type of readOnly or permanent.

         For a storage type of permanent, none of the columns have
         to be writable."
    DEFVAL { nonVolatile }
    ::= { ipiaIpsecProposalsEntry 6 }

ipiaIpsecPropRowStatus OBJECT-TYPE
    SYNTAX      RowStatus
    MAX-ACCESS  read-create
    STATUS      current
    DESCRIPTION
        "This object indicates the conceptual status of this row.

         The value of this object has no effect on whether other
         objects in this conceptual row can be modified.

         This row MUST NOT be set to active until the corresponding
         row(s) in the ipiaIpsecTransformsTable exists and is
         active.

         If active, this object MUST remain active unless one of the
         following two conditions are met.  An attempt to set it to
         anything other than active while the following conditions
         are not met MUST result in an inconsistentValue error.  The
         two conditions are:

         I.  No active row in the ipiaIkeActionProposalTable exists
             which has a matching ipiaIpsecPropName.

         II. Or at least one other active row in this table has a
             matching ipiaIpsecPropName."
    ::= { ipiaIpsecProposalsEntry 7 }

--
-- ipiaIpsecTransformsTable
--


ipiaIpsecTransformsTable OBJECT-TYPE
    SYNTAX      SEQUENCE OF IpiaIpsecTransformsEntry
    MAX-ACCESS  not-accessible
    STATUS      current
    DESCRIPTION
        "This table lists the IPsec proposals contained within a
         given IPsec action and the transforms within each of those
         proposals.  These proposals and transforms can then be used
         to create phase 2 negotiation proposals."
    ::= { ipiaConfigObjects 12 }

ipiaIpsecTransformsEntry OBJECT-TYPE
    SYNTAX      IpiaIpsecTransformsEntry
    MAX-ACCESS  not-accessible
    STATUS      current
    DESCRIPTION
        "An entry containing the information on an IPsec transform."
    INDEX       { ipiaIpsecTranType, ipiaIpsecTranName,
                  ipiaIpsecTranPriority }
    ::= { ipiaIpsecTransformsTable 1 }

IpiaIpsecTransformsEntry ::= SEQUENCE {
    ipiaIpsecTranType                        IpsecDoiSecProtocolId,
    ipiaIpsecTranName                        SnmpAdminString,
    ipiaIpsecTranPriority                    Integer32,
    ipiaIpsecTranTransformName               SnmpAdminString,
    ipiaIpsecTranLastChanged                 TimeStamp,
    ipiaIpsecTranStorageType                 StorageType,
    ipiaIpsecTranRowStatus                   RowStatus
}

ipiaIpsecTranType OBJECT-TYPE
    SYNTAX      IpsecDoiSecProtocolId
    MAX-ACCESS  not-accessible
    STATUS      current
    DESCRIPTION
        "The protocol type for this transform.  The protoIsakmp(1)
         value is not valid for this object."
    ::= { ipiaIpsecTransformsEntry 1 }

ipiaIpsecTranName OBJECT-TYPE
    SYNTAX      SnmpAdminString (SIZE(1..32))
    MAX-ACCESS  not-accessible
    STATUS      current
    DESCRIPTION
        "The name for this transform or group of transforms."
    ::= { ipiaIpsecTransformsEntry 2 }

ipiaIpsecTranPriority OBJECT-TYPE
    SYNTAX      Integer32 (0..65535)
    MAX-ACCESS  not-accessible
    STATUS      current
    DESCRIPTION
        "The priority level (AKA sequence level) of the this
         transform within the group of transforms (0 before 1,
         etc...).  This indicates the preference for which
         algorithms are requested when the list of transforms are
         sent to the remote host.  A lower number indicates a higher
         precedence."
    ::= { ipiaIpsecTransformsEntry 3 }

ipiaIpsecTranTransformName OBJECT-TYPE
    SYNTAX      SnmpAdminString (SIZE(1..32))
    MAX-ACCESS  read-create
    STATUS      current
    DESCRIPTION
        "The name for the given transform.  Depending on the value
         of ipiaIpsecTranType, this value is used to lookup the
         transform's specific parameters in the
         ipiaAhTransformTable, the ipiaEspTransformTable or the
         ipiaIpcompTransformTable."
    ::= { ipiaIpsecTransformsEntry 4 }

ipiaIpsecTranLastChanged OBJECT-TYPE
    SYNTAX      TimeStamp
    MAX-ACCESS  read-only
    STATUS      current
    DESCRIPTION
        "The value of sysUpTime when this row was last modified or
         created either through SNMP SETs or by some other external
         means."
    ::= { ipiaIpsecTransformsEntry 5 }

ipiaIpsecTranStorageType OBJECT-TYPE
    SYNTAX      StorageType
    MAX-ACCESS  read-create
    STATUS      current
    DESCRIPTION
        "The storage type for this row.  Rows in this table which
         were created through an external process MAY have a storage
         type of readOnly or permanent.

         For a storage type of permanent, none of the columns have
         to be writable."
    DEFVAL { nonVolatile }
    ::= { ipiaIpsecTransformsEntry 6 }

ipiaIpsecTranRowStatus OBJECT-TYPE
    SYNTAX      RowStatus
    MAX-ACCESS  read-create
    STATUS      current
    DESCRIPTION
        "This object indicates the conceptual status of this row.

         The value of this object has no effect on whether other
         objects in this conceptual row can be modified.

         This row MUST NOT be set to active until the corresponding
         row in the ipiaAhTransformTable, ipiaEspTransformTable or
         the ipiaIpcompTransformTable exists.

         If active, this object MUST remain active unless one of the
         following two conditions are met.  An attempt to set it to
         anything other than active while the following conditions
         are not met MUST result in an inconsistentValue error.  The
         two conditions are:

         I.  No active row in the IpiaIpsecProposalsTable exists
             which has a matching ipiaIpsecPropTransformsName.

         II. Or at least one other active row in this table has a
             matching ipiaIpsecPropTransformsName."
    ::= { ipiaIpsecTransformsEntry 7 }


--
-- IKE identity definition table
--

ipiaIkeIdentityTable OBJECT-TYPE
    SYNTAX      SEQUENCE OF IpiaIkeIdentityEntry
    MAX-ACCESS  not-accessible
    STATUS      current
    DESCRIPTION
        "IKEIdentity is used to represent the identities that are
         used for an IPProtocolEndpoint (or collection of
         IPProtocolEndpoints) to identify itself in IKE phase 1
         negotiations.  The column ipiaIkeActIdentityType and
         ipiaIkeIdentityContext in an ipiaIkeActionEntry together
         with the spdEndGroupInterface in the
         spdEndpointToGroupTable specifies the unique identity to
         use in a negotiation exchange."
    ::= { ipiaConfigObjects 13 }

ipiaIkeIdentityEntry OBJECT-TYPE
    SYNTAX      IpiaIkeIdentityEntry
    MAX-ACCESS  not-accessible
    STATUS      current
    DESCRIPTION
        "ikeIdentity lists the attributes of an IKE identity."

    INDEX { spdEndGroupInterface, ipiaIkeActIdentityType,
            ipiaIkeActIdentityContext }
    ::= { ipiaIkeIdentityTable 1 }

IpiaIkeIdentityEntry ::= SEQUENCE {
    ipiaIkeIdCredentialName                 SnmpAdminString,
    ipiaIkeIdLastChanged                    TimeStamp,
    ipiaIkeIdStorageType                    StorageType,
    ipiaIkeIdRowStatus                      RowStatus
}

ipiaIkeIdCredentialName OBJECT-TYPE
    SYNTAX      SnmpAdminString (SIZE(0..32))
    MAX-ACCESS  read-create
    STATUS      current
    DESCRIPTION
        "This value is used as an index into the
         ipiaCredentialFilterTable to look up the actual credential
         value and other credential information.

         For ID's without associated credential information, this
         value is left blank.

         For ID's that are address types, this value MAY be left
         blank and the associated IPProtocolEndpoint or appropriate
         member of the Collection of endpoints is used."
    ::= { ipiaIkeIdentityEntry 1 }

ipiaIkeIdLastChanged OBJECT-TYPE
    SYNTAX      TimeStamp
    MAX-ACCESS  read-only
    STATUS      current
    DESCRIPTION
        "The value of sysUpTime when this row was last modified or
         created either through SNMP SETs or by some other external
         means."
    ::= { ipiaIkeIdentityEntry 2 }

ipiaIkeIdStorageType OBJECT-TYPE
    SYNTAX      StorageType
    MAX-ACCESS  read-create
    STATUS      current
    DESCRIPTION
        "The storage type for this row.  Rows in this table which
         were created through an external process MAY have a storage
         type of readOnly or permanent.

         For a storage type of permanent, none of the columns have
         to be writable."
    DEFVAL { nonVolatile }
    ::= { ipiaIkeIdentityEntry 3 }

ipiaIkeIdRowStatus OBJECT-TYPE
    SYNTAX      RowStatus
    MAX-ACCESS  read-create
    STATUS      current
    DESCRIPTION
        "This object indicates the conceptual status of this row.

         The value of this object has no effect on whether other
         objects in this conceptual row can be modified.

         If active, this object MUST remain active if it is
         referenced by an active row in another table.  An attempt
         to set it to anything other than active while it is
         referenced by an active row in another table MUST result in
         an inconsistentValue error."
    ::= { ipiaIkeIdentityEntry 4 }

END
